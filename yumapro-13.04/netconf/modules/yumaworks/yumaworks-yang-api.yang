module yumaworks-yang-api {

  namespace "http://yumaworks.com/ns/yumaworks-yang-api";

  prefix "yapi";
  
  import ietf-inet-types { prefix inet; }  
  import yuma-ncx { prefix ncx; }
  import yumaworks-extensions { prefix ywx; }

  organization "YumaWorks, Inc.";

  contact
    "Support <support@yumaworks.com>";

  description
    "This module contains abstract object definitions for 
     the YANG-API protocol.";

  revision 2013-02-06 {
    description 
       "Rewrite to match draft-bierman-netconf-yang-api-01.txt";
  }

  revision 2012-06-28 {
    description 
       "Initial version";
  }

  extension optional-key {
    description 
      "This extension is used to allow the client to create
       a new instance of a resource without providing a
       value for the key leaf containing this statement.
       This extension is ignored for NETCONF, and only
       applies to YANG-API resources and fields.
       This extension is ignored unless it appears
       directly within a 'leaf' data definition statement.";
  }

  container yang-api {
    ncx:abstract;
    ncx:hidden;

    container datastore {
      ncx:root;
    }
    container modules {
      leaf-list module {
        type inet:uri;
      }
    }
    container operations {
      ywx:rpc-root;
    }
    leaf version {
      type string;
    }
  }
      
  container query {
    ncx:abstract;
    ncx:hidden;
    description "YANG-API Query String Parameters";

    leaf config {
      type boolean;
      default true;
      description "Get config true or config false nodes.";
    }

    leaf depth {
      type union {
        type enumeration {
          enum unbounded;
        }
        type uint32 {
          range "1..max";
        }
      }
      default 2;   // set to 1 in draft-01!
      description "Resource retrieval depth requested";
    }

    leaf format {
      type enumeration {
        enum xml;
        enum json;
      }
      default json;
      description "Response encoding requested";
    }

    leaf insert {
      type enumeration {
        enum first;
        enum last;
        enum before;
        enum after;
      }
      default last;
      description "Insert mode for an edit operation";
    }

    leaf point {
      ywx:urlpath;
      type string {
        length "1 .. max";
      }
      description 
        "YANG-API instance identifier for the insertion point
         node for the edit operation.";
    }

    leaf select {
      // ywx:urlpath;   !! NOT IMPLEMENTED AS A URLPATH!!!
      type string {
        length "1 .. max";
      }
      description
        "An XPath expression that will be evaluated using the
         target resource instance as the context node and the
         document root. It is expected to return a node-set
         result representing the descendants within the context
         node that should be returned in a GET response.";

    }

    leaf test {
      // ywx:urlpath;   !! NOT IMPLEMENTED AS A URLPATH!!!
      type string {
        length "1 .. max";
      }
    }

  }
  
}
