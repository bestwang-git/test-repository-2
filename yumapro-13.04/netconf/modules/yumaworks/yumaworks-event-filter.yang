module yumaworks-event-filter {

  namespace "http://yumaworks.com/ns/yumaworks-event-filter";

  prefix "ef";
  
  import yuma-types { prefix yt; }

  organization "YumaWorks, Inc.";

  contact
    "Support <support@yumaworks.com>";

  description
    "This module contains data structures representing 
     notification event filters to be applied to
     the generation of events into a notification stream.";
                
  revision 2012-08-17 {
    description 
       "Initial version";
  }

  container event-filters {
     presence 
      "If this node is present then the event filtering
       service is enabled.";

     list event-filter {
      description 
        "A list of notification event filters.";

      key "module event";

      leaf module {
        type yt:NcxName;
        description
          "The YANG module name for the this entry.";
      }

      leaf event {
        type yt:NcxName;
        description
          "The notification event name for this entry.";
      }

      leaf max-rate {
        type uint32;
        default 0;
        units "events-per-minute";
        description
          "The maximum number of notifications of the specified
           event type to generate per minute.
           The value 0 indicates that no notifications of this
           event type will be generated.";
      }
    }
  }


}
